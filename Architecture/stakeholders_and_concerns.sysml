package StakeholdersDefinitionPackage {

    part def AcademicInstitutions {
        doc /* Universities involved directly in the HEALIOS mission. The core HEALIOS Team is composed of students enrolled in these institutions. Interested in providing academic supervision and resources to improve the institution visibility, qualification, and research capabilities. */
    }

    part def ResearchInstitutes {
        doc /* Research institutions involved, directly and indirectly, in the HEALIOS mission. This includes private companies or government laboratories. Academic institutions may also be included, if their role is not directly conteted to the student status of the core HEALIOS Team.*/
    }

    part def EuropeanSpaceAgency {
        doc /* The intergovernmental organization that develops satellite-based technologies; which provides the framework and support for the mission. Interested in supporting univeristy engaement in space exploration and satellite technology development. */
    }

    part def Manufacturers {
        doc /* Companies manufacturing satellite components, including solar cells. Interested in providing components for space missions. */
    }
    part def HEALIOS_Team_Community {
        doc /* The core team responsible for the HEALIOS mission. Interested in successfully executing the mission objectives and advancing space technology. */
    }
    part def RegulatoryBodies {
        doc /* Organizations that regulate space activities and satellite operations. Interested in ensuring compliance with international space law and safety standards. */
    }

    part def <FYS> ESAFlyYourSatelliteProgramme specializes EuropeanSpaceAgency {
        doc /* The ESA program that supports university satellite projects. Interested in ensuring the success of the HEALIOS mission and fostering educational opportunities in space technology. */
    }
    part def <CSF> ESACubeSatSupportFacility specializes EuropeanSpaceAgency {
        doc /* The ESA facility that provides support for CubeSat missions, including testing and integration services. Interested in ensuring the technical success and testing campaign of the HEALIOS mission. */
    }
    part def CubeSatCommunity specializes Manufacturers {
        doc /* The community of manufacturers and developers focused on CubeSat technology. Interested in advancing CubeSat visibility in space sector; provide CubeSat Design Specification - guide for the HEALIOS mission. */
    }

    part def SatelliteCOTSManufacturers specializes Manufacturers {
        doc /* Companies that provide commercial off-the-shelf (COTS) components for satellite construction. Interested in providing reliable and cost-effective components for space missions, including the HEALIOS mission. */
    }
    
    part def <GUT> GdanskUniversityOfTechnology specializes AcademicInstitutions {
        doc /* The university collaborating on the HEALIOS mission.*/
    }

    part def <HSB> HSBHochschuleBremen specializes AcademicInstitutions {
        doc /* The university collaborating on the HEALIOS mission. */
    }
    
    part def HEALIOSTeamCommunity specializes HEALIOS_Team_Community {
        doc /* The broader community of students, researchers, and professionals involved in the HEALIOS mission. Interested in the success of the mission and the advancement of space technology. Beside the core team, this includes collaborators and supporters. */
    }

    part def PerovskiteResearchInstitutes specializes ResearchInstitutes {
        doc /* Research institutions focused on perovskite solar cell technology. Interested in advancing the performance and space-readiness of perovskite solar cells. Benfit from data generated by the mission. */
    }
    part def PerovskiteSolarCellManufacturers specializes Manufacturers {
        doc /* Companies manufacturing perovskite solar cells. Interested in providing high-performance solar cells for space applications and advancing the commercial viability of perovskite technology. Benfit from maturing TRL of the perovskite solar cells in space. */
    }    
    part def <IARU> InternationalAmateurRadioUnion specializes RegulatoryBodies {
        doc /* The international organization that coordinates amateur radio activities, including satellite communications. Interested in ensuring the proper use of radio frequencies and promoting amateur radio involvement in space missions. */
    }
    part def <ITU> InternationalTelecommunicationUnion specializes RegulatoryBodies {
        doc /* The United Nations specialized agency for information and communication technologies, including satellite communications. Interested in regulating the use of radio frequencies and ensuring compliance with international telecommunications standards. */
    }
    part def <LSP> LaunchServiceProvider specializes RegulatoryBodies {
        doc /* Companies or organizations that provide launch services for satellites. Interested in providing reliable and cost-effective launch options for space missions, including the HEALIOS mission. One of the most probable launch provider is currently SpaceX. */
    }
    part def <UNOOSA> UnitedNationsOfficeForOuterSpaceAffairs specializes RegulatoryBodies {
        doc /* The United Nations office responsible for promoting international cooperation in the peaceful use and exploration of outer space. Interested in ensuring compliance with international space law and promoting the benefits of space activities. */
    }
}

package StakeholderConcernsPackage {

    private import ScalarValues::*;
    private import StakeholdersDefinitionPackage::*;
    private import MissionPackage::*;

    concern def EducationalValueConcern {

        subject HEALIOS_Mission : MissionSegments; 
        
        require constraint {
            doc /* The mission shall provide hands-on experience in satellite development, integration, and operations to the student team to fulfill academic qualification requirements. */
        }

        stakeholder HEALIOS_Team_Community : HEALIOSTeamCommunity;
        stakeholder GUT : GdanskUniversityOfTechnology;
        stakeholder HSB : HSBHochschuleBremen;
        stakeholder FYS : ESAFlyYourSatelliteProgramme;
    }

    concern def InstitutionalVisibilityConcern {
        subject HEALIOS_Mission : MissionSegments;

        require constraint {
            doc /* The mission shall demonstrate the research capabilities of the participating universities and ESA programs to the broader aerospace community. */
        }

        stakeholder GUT : GdanskUniversityOfTechnology;
        stakeholder HSB : HSBHochschuleBremen;
        stakeholder FYS : ESAFlyYourSatelliteProgramme;
    }

    concern def PerovskiteTRLAdvancementConcern {
        subject HEALIOS_Mission : MissionSegments;
        
        require constraint {
            doc /* The mission shall validate the performance Perovskite solar cells in the Low Earth Orbit (LEO) environment to increase their Technology Readiness Level (TRL). */
        }

        stakeholder Perovskite_Manufacturers : PerovskiteSolarCellManufacturers;
        stakeholder Perovskite_Researchers : PerovskiteResearchInstitutes;
    }

    concern def PerovskiteInvestigationConcern {
        subject HEALIOS_Mission : MissionSegments;
        
        require constraint {
            doc /* The mission shall investigate the self-healing behavior of Perovskite Solar Cells induced by reverse-bias voltage during eclipse phases, and quantify their degradation in the space environment (Voc, Isc, MPP). */
        }

        stakeholder Perovskite_Researchers : PerovskiteResearchInstitutes;
        stakeholder HEALIOS_Team_Community : HEALIOSTeamCommunity;
    }

    concern def ComparativeStudyConcern {
        subject HEALIOS_Mission : MissionSegments;

        require constraint {
            doc /* The mission shall compare degradation rates between Perovskite samples and traditional space-graded solar cells (e.g., silicon) under identical space environment exposure to benchmark performance. */
        }

        stakeholder Perovskite_Researchers : PerovskiteResearchInstitutes;
        stakeholder Perovskite_Manufacturers : PerovskiteSolarCellManufacturers;
    }

    concern def DataAcquisitionConcern {
        subject HEALIOS_Mission : MissionSegments;

        require constraint {
            doc /* The mission shall ensure validated data from the payload is acquired with sufficient context, resolution and accuracy to analyse solar cell efficiency over time. */
        }

        stakeholder Perovskite_Researchers : PerovskiteResearchInstitutes;
        stakeholder HEALIOS_Team_Community : HEALIOSTeamCommunity;
    }

    concern def DataAvailabilityConcern {
        subject HEALIOS_Mission : MissionSegments;

        require constraint {
            doc /* The mission shall ensure that scientific results and telemetry are processed, archived, and made accessible to the scientific community. */
        }

        stakeholder Perovskite_Researchers : PerovskiteResearchInstitutes;
        stakeholder HEALIOS_Team_Community : HEALIOSTeamCommunity;
    }

    concern def SafetyConcern {
        subject HEALIOS_Mission : MissionSegments;
        
        
        require constraint {
            doc /* The mission shall ensure the safety of the launch vehicle, transport means, personnel, and testing facilities by adhering to hazard control measures and safety requirements. */
        }

        stakeholder Launch_Providers : LaunchServiceProvider;
        stakeholder CSF : ESACubeSatSupportFacility;
    }

    concern def CubeSatStandardComplianceConcern {
        subject HEALIOS_Mission : MissionSegments;
        
        require constraint {
            doc /* The mission architecture shall conform to the CubeSat Design Specification (CDS) to ensure physical and functional compatibility with the deployment system. */
        }

        stakeholder CubeSat_Community : CubeSatCommunity;
        stakeholder Launch_Providers : LaunchServiceProvider;
        stakeholder CSF : ESACubeSatSupportFacility;
    }

    concern def SpaceDebrisMitigationConcern {
        subject HEALIOS_Mission : MissionSegments;

        require constraint {
            doc /* The mission shall be designed to minimize space debris generation and ensure orbital decay within the regulatory timeframe after the end of operations. */
        }

        stakeholder UNOOSA : UnitedNationsOfficeForOuterSpaceAffairs;
        stakeholder ESA : EuropeanSpaceAgency;
    }

    concern def ComponentReliabilityConcern {
        subject HEALIOS_Mission : MissionSegments;
        
        require constraint {
            doc /* The mission shall ensure the survival and operational integrity of the system in the Low Earth Orbit (LEO) environment for the intended duration. */
        }

        stakeholder Satellite_COTS_Providers : SatelliteCOTSManufacturers;
        stakeholder HEALIOS_Team_Community : HEALIOSTeamCommunity;
        stakeholder CSF : ESACubeSatSupportFacility;
    }

    concern def FrequencyAllocationConcern {
        subject HEALIOS_Mission : MissionSegments;
        
        require constraint {
            doc /* The mission shall operate within allocated radio frequency bands and comply with international telecommunication regulations to prevent interference. */
        }

        stakeholder ITU : InternationalTelecommunicationUnion;
        stakeholder IARU : InternationalAmateurRadioUnion;
    }

    concern def LinkCompatibilityConcern {
        subject HEALIOS_Mission : MissionSegments;

        require constraint {
            doc /* The mission shall establish a compatible and reliable communication link between the space and ground segments to support operations. */
        }

        stakeholder HEALIOS_Team_Community : HEALIOSTeamCommunity;
        stakeholder IARU : InternationalAmateurRadioUnion;
    }

    concern def CommandSecurityConcern {
        subject HEALIOS_Mission : MissionSegments;

        require constraint {
            doc /* The mission shall implement security measures to prevent unauthorized access or control of the space and ground segments. */
        }

        stakeholder ITU : InternationalTelecommunicationUnion;
        stakeholder HEALIOS_Team_Community : HEALIOSTeamCommunity;
    }

    concern def AmateurRadioAccessConcern {
        subject HEALIOS_Mission : MissionSegments;

        require constraint {
            doc /* The mission shall engage the global amateur radio community by enabling the open reception and decoding of public beacon telemetry. */
        }

        stakeholder IARU : InternationalAmateurRadioUnion;
        stakeholder CubeSat_Community : CubeSatCommunity;
    }

    concern def ProgrammaticComplianceConcern {
        subject HEALIOS_Mission : MissionSegments;

        require constraint {
            doc /* The mission shall adhere to the programmatic schedules, review milestones, and documentation standards mandated by the ESA Fly Your Satellite! programme. */
        }

        stakeholder FYS : ESAFlyYourSatelliteProgramme;
        stakeholder HEALIOS_Team_Community : HEALIOSTeamCommunity;
    }

    concern def RegistrationComplianceConcern {
        subject HEALIOS_Mission : MissionSegments;

        require constraint {
            doc /* The mission shall comply with all registration requirements for space objects, including UN registration and any applicable national regulations. */
        }

        stakeholder UNOOSA : UnitedNationsOfficeForOuterSpaceAffairs;
        stakeholder HEALIOS_Team_Community : HEALIOSTeamCommunity;
    }
}
