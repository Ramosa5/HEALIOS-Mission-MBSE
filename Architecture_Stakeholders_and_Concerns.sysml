// Traceability: The frame keyword formally traces the engineering metrics in the high-level mission requirements back to the stakeholder's text-based concern.

package StakeholdersDefinitionPackage {
    private import MissionPackage::*;
    private import HealiosMissionInstancePackage::*;
    private import ISQ::*;

    part def ESAProgramme {
        doc /* The ESA set of ESA programmes. */
    }
    part def ESAFacility {
        doc /* The ESA set of facilities that provide support for missions. */
    }
    
    part def <FYS> ESAFlyYourSatelliteProgramme specializes ESAProgramme {
        doc /* The ESA program that supports university satellite projects. Interested in ensuring the success of the HEALIOS mission and fostering educational opportunities in space technology. */
    }
    part def <CSF> ESACubeSatSupportFacility specializes ESAFacility {
        doc /* The ESA facility that provides support for CubeSat missions, including testing and integration services. Interested in ensuring the technical success and testing campaign of the HEALIOS mission. */
    }

    part def <ESA> EuropeanSpaceAgency {
        doc /* The intergovernmental organisation that develops satellite-based technologies. It provides the framework and support for the mission. Interested in supporting the university engagement in space exploration and satellite technology development. */
        part ESA_Programmes : ESAProgramme[*];
        part ESA_Facilities : ESAFacility[*];

        part Fly_Your_Satellite_programme : ESAFlyYourSatelliteProgramme subsets ESA_Programmes;
        part CubeSat_Support_Facility : ESACubeSatSupportFacility subsets ESA_Facilities;
    }

    part def AcademicInstitutions {
        doc /* Universities involved directly in the HEALIOS mission. The core HEALIOS Team is composed of students enrolled in these institutions. Interested in providing academic supervision and resources to improve the institution visibility, qualification, and research capabilities. */
    }

    part def ResearchInstitutes {
        doc /* Research institutions involved, directly and indirectly, in the HEALIOS mission. This includes private companies or government laboratories. Academic institutions may also be included, if their role is not directly conteted to the student status of the core HEALIOS Team.*/
    }

    part def Manufacturers {
        doc /* Companies manufacturing satellite components, including solar cells. Interested in providing components for space missions. */
    }
    part def HEALIOSTeam {
        doc /* The core team responsible for the HEALIOS mission. Interested in successfully executing the mission objectives and advancing space technology. */

    }
    part def RegulatoryBodies {
        doc /* Organizations that regulate space activities and satellite operations. Interested in ensuring compliance with international space law and safety standards. */
    }

    part def CubeSatCommunity specializes Manufacturers {
        doc /* The community of manufacturers and developers focused on CubeSat technology. Interested in advancing CubeSat visibility in space sector; provide CubeSat Design Specification - guide for the HEALIOS mission. */
    }

    part def SatelliteCOTSManufacturers specializes Manufacturers {
        doc /* Companies that provide commercial off-the-shelf (COTS) components for satellite construction. Interested in providing reliable and cost-effective components for space missions, including the HEALIOS mission. */
    }
    
    part def <GUT> GdanskUniversityOfTechnology specializes AcademicInstitutions {
        doc /* The university collaborating on the HEALIOS mission.*/
    }

    part def <HSB> HSBHochschuleBremen specializes AcademicInstitutions {
        doc /* The university collaborating on the HEALIOS mission. */
    }
    
    part def HEALIOSTeamCommunity specializes HEALIOSTeam {
        doc /* The broader community of students, researchers, and professionals involved in the HEALIOS mission. Interested in the success of the mission and the advancement of space technology. Beside the core team, this includes collaborators and supporters. */
    }

    part def PerovskiteResearchInstitutes specializes ResearchInstitutes {
        doc /* Research institutions focused on perovskite solar cell technology. Interested in advancing the performance and space-readiness of perovskite solar cells. Benfit from data generated by the mission. */
    }
    part def PerovskiteSolarCellManufacturers specializes Manufacturers {
        doc /* Companies manufacturing perovskite solar cells. Interested in providing high-performance solar cells for space applications and advancing the commercial viability of perovskite technology. Benfit from maturing TRL of the perovskite solar cells in space. */
    }    
    part def <IARU> InternationalAmateurRadioUnion specializes RegulatoryBodies {
        doc /* The international organization that coordinates amateur radio activities, including satellite communications. Interested in ensuring the proper use of radio frequencies and promoting amateur radio involvement in space missions. */
    }
    part def <ITU> InternationalTelecommunicationUnion specializes RegulatoryBodies {
        doc /* The United Nations specialized agency for information and communication technologies, including satellite communications. Interested in regulating the use of radio frequencies and ensuring compliance with international telecommunications standards. */
    }
    part def <LSP> LaunchServiceProvider specializes RegulatoryBodies {
        doc /* Companies or organizations that provide launch services for satellites. Interested in providing reliable and cost-effective launch options for space missions, including the HEALIOS mission. One of the most probable launch provider is currently SpaceX. */
    }
    part def <UNOOSA> UnitedNationsOfficeForOuterSpaceAffairs specializes RegulatoryBodies {
        doc /* The United Nations office responsible for promoting international cooperation in the peaceful use and exploration of outer space. Interested in ensuring compliance with international space law and promoting the benefits of space activities. */
    }
}

package ConcernsDefinitionPackage {

    private import ScalarValues::*;
    private import StakeholdersDefinitionPackage::*;
    private import StakeholderConcernsPackage::*;
    private import MissionPackage::*;

    concern def EducationalValueConcern {

        subject HEALIOS_Mission references HealiosMissionInstancePackage::HEALIOS_Mission;
    
        require constraint {
            doc /* The mission shall provide hands-on experience in satellite development, integration, and operations to the student team. */
        }

        stakeholder HEALIOS_Team_Community references StakeholderConcernsPackage::HEALIOS_Team_Community;
        stakeholder Gdansk_University_Of_Technology references StakeholderConcernsPackage::Gdansk_University_Of_Technology;
        stakeholder HSB_Hochschule_Bremen references StakeholderConcernsPackage::HSB_Hochschule_Bremen;
        stakeholder Fly_Your_Satellite_programme references StakeholderConcernsPackage::European_Space_Agency.Fly_Your_Satellite_programme;
    }

    concern def InstitutionalVisibilityConcern {
        subject HEALIOS_Mission references HealiosMissionInstancePackage::HEALIOS_Mission;

        require constraint {
            doc /* The mission shall demonstrate research capabilities of the participating universities and ESA programmes to the broader aerospace community. */
        }

        stakeholder Fly_Your_Satellite_programme references StakeholderConcernsPackage::European_Space_Agency.Fly_Your_Satellite_programme;
        stakeholder Gdansk_University_Of_Technology references StakeholderConcernsPackage::Gdansk_University_Of_Technology;
        stakeholder HSB_Hochschule_Bremen references StakeholderConcernsPackage::HSB_Hochschule_Bremen;
    }

    concern def PerovskiteTRLAdvancementConcern {
        subject HEALIOS_Mission references HealiosMissionInstancePackage::HEALIOS_Mission;
        
        require constraint {
            doc /* The mission shall validate the performance Perovskite solar cells in the Low Earth Orbit environment to increase their Technology Readiness Level. */
        }

        stakeholder Perovskite_Manufacturers references StakeholderConcernsPackage::Perovskite_Manufacturers;
        stakeholder Perovskite_Researchers references StakeholderConcernsPackage::Perovskite_Researchers;
    }

    concern def PerovskiteInvestigationConcern {
        subject HEALIOS_Mission references HealiosMissionInstancePackage::HEALIOS_Mission;
        
        require constraint {
            doc /* The mission shall investigate the self-healing behavior of Perovskite Solar Cells induced by reverse-bias voltage during eclipse phases, and quantify their degradation in the space environment (Voc, Isc, MPP). */
        }

        stakeholder Perovskite_Manufacturers references StakeholderConcernsPackage::Perovskite_Manufacturers;
        stakeholder Perovskite_Researchers references StakeholderConcernsPackage::Perovskite_Researchers;
        stakeholder HEALIOS_Team_Community references StakeholderConcernsPackage::HEALIOS_Team_Community;
    }

    concern def ComparativeStudyConcern {
        subject HEALIOS_Mission references HealiosMissionInstancePackage::HEALIOS_Mission;

        require constraint {
            doc /* The mission shall compare degradation rates between Perovskite samples and traditional space-graded solar cells (e.g., silicon) under identical space environment exposure to benchmark performance. */
        }

        stakeholder Perovskite_Researchers references StakeholderConcernsPackage::Perovskite_Researchers;
        stakeholder Perovskite_Manufacturers references StakeholderConcernsPackage::Perovskite_Manufacturers;
        stakeholder HEALIOS_Team_Community references StakeholderConcernsPackage::HEALIOS_Team_Community;
    }

    concern def DataAcquisitionConcern {
        subject HEALIOS_Mission references HealiosMissionInstancePackage::HEALIOS_Mission;

        require constraint {
            doc /* The mission shall ensure validated data from the payload is acquired with sufficient context, resolution and accuracy to analyse solar cell efficiency over time. */
        }

        stakeholder Perovskite_Researchers references StakeholderConcernsPackage::Perovskite_Researchers;
        stakeholder HEALIOS_Team_Community references StakeholderConcernsPackage::HEALIOS_Team_Community;
    }

    concern def DataAvailabilityConcern {
        subject HEALIOS_Mission references HealiosMissionInstancePackage::HEALIOS_Mission;

        require constraint {
            doc /* The mission shall ensure that scientific results and telemetry are processed, archived, and made accessible to the scientific community. */
        }

        stakeholder Perovskite_Researchers references StakeholderConcernsPackage::Perovskite_Researchers;
        stakeholder HEALIOS_Team_Community references StakeholderConcernsPackage::HEALIOS_Team_Community;
    }

    concern def SafetyConcern {
        subject HEALIOS_Mission references HealiosMissionInstancePackage::HEALIOS_Mission;
        
        
        require constraint {
            doc /* The mission shall ensure the safety of the launch vehicle, transport means, personnel, and testing facilities by adhering to hazard control measures and safety requirements. */
        }

        stakeholder Launch_Providers : LaunchServiceProvider;
        stakeholder CSF references StakeholderConcernsPackage::European_Space_Agency.CubeSat_Support_Facility;
        stakeholder HEALIOS_Team_Community references StakeholderConcernsPackage::HEALIOS_Team_Community;
    }

    concern def CubeSatStandardComplianceConcern {
        subject HEALIOS_Mission references HealiosMissionInstancePackage::HEALIOS_Mission;
        
        require constraint {
            doc /* The mission architecture shall conform to the CubeSat Design Specification (CDS) to ensure physical and functional compatibility with the deployment system. */
        }

        stakeholder CubeSat_Community references StakeholderConcernsPackage::CubeSat_Community;
        stakeholder Launch_Providers references StakeholderConcernsPackage::Launch_Providers;
        stakeholder CSF references StakeholderConcernsPackage::European_Space_Agency.CubeSat_Support_Facility;
        stakeholder Fly_Your_Satellite_programme references StakeholderConcernsPackage::European_Space_Agency.Fly_Your_Satellite_programme;
    }

    concern def SpaceDebrisMitigationConcern {
        subject HEALIOS_Mission references HealiosMissionInstancePackage::HEALIOS_Mission;

        require constraint {
            doc /* The mission shall be designed to minimize space debris generation and ensure orbital decay within the regulatory timeframe after the end of operations. */
        }

        stakeholder UNOOSA references StakeholderConcernsPackage::UNOOSA;
        stakeholder ESA references StakeholderConcernsPackage::European_Space_Agency;
    }

    concern def ComponentReliabilityConcern {
        subject HEALIOS_Mission references HealiosMissionInstancePackage::HEALIOS_Mission;
        
        require constraint {
            doc /* The mission shall ensure the survival and operational integrity of the system in the Low Earth Orbit (LEO) environment for the intended duration. */
        }

        stakeholder Satellite_COTS_Providers references StakeholderConcernsPackage::Satellite_COTS_Manufacturers;
        stakeholder HEALIOS_Team_Community references StakeholderConcernsPackage::HEALIOS_Team_Community;
        stakeholder CSF references StakeholderConcernsPackage::European_Space_Agency.CubeSat_Support_Facility;
    }

    concern def FrequencyAllocationConcern {
        subject HEALIOS_Mission references HealiosMissionInstancePackage::HEALIOS_Mission;
        
        require constraint {
            doc /* The mission shall operate within allocated radio frequency bands and comply with international telecommunication regulations to prevent interference. */
        }

        stakeholder ITU references StakeholderConcernsPackage::ITU;
        stakeholder IARU references StakeholderConcernsPackage::IARU;
    }

    concern def LinkCompatibilityConcern {
        subject HEALIOS_Mission references HealiosMissionInstancePackage::HEALIOS_Mission;

        require constraint {
            doc /* The mission shall establish a compatible and reliable communication link between the space and ground segments to support operations. */
        }

        stakeholder HEALIOS_Team_Community references StakeholderConcernsPackage::HEALIOS_Team_Community;
        stakeholder IARU references StakeholderConcernsPackage::IARU;
    }

    concern def CommandSecurityConcern {
        subject HEALIOS_Mission references HealiosMissionInstancePackage::HEALIOS_Mission;

        require constraint {
            doc /* The mission shall implement security measures to prevent unauthorized access or control of the space and ground segments. */
        }

        stakeholder ITU references StakeholderConcernsPackage::ITU;
        stakeholder HEALIOS_Team_Community references StakeholderConcernsPackage::HEALIOS_Team_Community;
    }

    concern def AmateurRadioAccessConcern {
        subject HEALIOS_Mission references HealiosMissionInstancePackage::HEALIOS_Mission;

        require constraint {
            doc /* The mission shall engage the global amateur radio community by enabling the open reception and decoding of public beacon telemetry. */
        }

        stakeholder IARU references StakeholderConcernsPackage::IARU;
        stakeholder CubeSat_Community references StakeholderConcernsPackage::CubeSat_Community;
        stakeholder HEALIOS_Team_Community references StakeholderConcernsPackage::HEALIOS_Team_Community;
    }

    concern def ProgrammaticComplianceConcern {
        subject HEALIOS_Mission references HealiosMissionInstancePackage::HEALIOS_Mission;

        require constraint {
            doc /* The mission shall adhere to the programmatic schedules, review milestones, and documentation standards mandated by the ESA Fly Your Satellite! programme. */
        }

        stakeholder FYS references StakeholderConcernsPackage::European_Space_Agency.Fly_Your_Satellite_programme;
        stakeholder HEALIOS_Team_Community references StakeholderConcernsPackage::HEALIOS_Team_Community;
    }

    concern def TeamCompositionConcern {
        subject HEALIOS_Mission references HealiosMissionInstancePackage::HEALIOS_Mission;

        require constraint {
            doc /* The mission team shall consist of a core group of at least 8 eligible students (minimum 4 at Master/PhD level) and a minimum of 2 supervisors covering the roles of endorsing professor, team leader, and system engineer. The team must continuously comply with ESA Fly Your Satellite! citizenship, age (18-32), and academic enrollment criteria throughout the project lifecycle. */
        }

        stakeholder Fly_Your_Satellite_programme references StakeholderConcernsPackage::European_Space_Agency.Fly_Your_Satellite_programme;
        stakeholder HEALIOS_Team_Community references StakeholderConcernsPackage::HEALIOS_Team_Community;
        stakeholder Gdansk_University_Of_Technology references StakeholderConcernsPackage::Gdansk_University_Of_Technology;
        stakeholder HSB_Hochschule_Bremen references StakeholderConcernsPackage::HSB_Hochschule_Bremen;
    }

    concern def RegistrationComplianceConcern {
        subject HEALIOS_Mission references HealiosMissionInstancePackage::HEALIOS_Mission;

        require constraint {
            doc /* The mission shall comply with all registration requirements for space objects, including UN registration and any applicable national regulations. */
        }

        stakeholder UNOOSA references StakeholderConcernsPackage::UNOOSA;
        stakeholder HEALIOS_Team_Community references StakeholderConcernsPackage::HEALIOS_Team_Community;
    }
}

package StakeholderConcernsPackage {
    private import StakeholdersDefinitionPackage::*;
    private import ConcernsDefinitionPackage::*;
    private import MissionPackage::*;

    part European_Space_Agency : ESA;
    part Gdansk_University_Of_Technology : GUT;
    part HSB_Hochschule_Bremen : HSB;
    part CubeSat_Community : CubeSatCommunity;
    part Satellite_COTS_Providers : SatelliteCOTSManufacturers;
    part HEALIOS_Team_Community : HEALIOSTeamCommunity;
    part Perovskite_Manufacturers : PerovskiteSolarCellManufacturers;
    part Perovskite_Researchers : PerovskiteResearchInstitutes;
    part UNOOSA : UnitedNationsOfficeForOuterSpaceAffairs;
    part ITU : InternationalTelecommunicationUnion;
    part IARU : InternationalAmateurRadioUnion;
    part Launch_Providers : LaunchServiceProvider;
    part Satellite_COTS_Manufacturers : SatelliteCOTSManufacturers;
    
    part Educational_Value_Concern : EducationalValueConcern {
        doc /* Framed by the Mission Requirements: R_M_009, R_M_011, R_M_013 */
    }
    part Institutional_Visibility_Concern : InstitutionalVisibilityConcern {
        doc /* Framed by the Mission Requirements: R_M_009, R_M_010, R_M_011, R_M_012, R_M_013 */
    }
    part Perovskite_TRL_Advancement_Concern : PerovskiteTRLAdvancementConcern {
        doc /* Framed by the Mission Requirements: R_M_001, R_M_002, R_M_007 */
    }
    part Perovskite_Investigation_Concern : PerovskiteInvestigationConcern {
        doc /* Framed by the Mission Requirements: R_M_001 */
    }
    part Comparative_Study_Concern : ComparativeStudyConcern {
        doc /* Framed by the Mission Requirements: R_M_001, R_M_005 */
    }
    part Data_Acquisition_Concern : DataAcquisitionConcern {
        doc /* Framed by the Mission Requirements: R_M_001 */
    }
    part Data_Availability_Concern : DataAvailabilityConcern {
        doc /* Framed by the Mission Requirements: R_M_001, R_M_005, */
    }
    part Safety_Concern : SafetyConcern {
        doc /* Framed by the Mission Requirements: R_M_015, R_M_016 */
    }
    part CubeSat_Standard_Compliance_Concern : CubeSatStandardComplianceConcern {
        doc /* Framed by the Mission Requirements: R_M_003 */
    }
    part Space_Debris_Mitigation_Concern : SpaceDebrisMitigationConcern {
        doc /* Framed by the Mission Requirements: R_M_008, R_M_018 */
    }
    part Component_Reliability_Concern : ComponentReliabilityConcern {
        doc /* Framed by the Mission Requirements: R_M_002, R_M_007, R_M_012, R_M_019 */
    }
    part Frequency_Allocation_Concern : FrequencyAllocationConcern {
        doc /* Framed by the Mission Requirements: R_M_017 */
    }
    part Link_Compatibility_Concern : LinkCompatibilityConcern {
        doc /* Framed by the Mission Requirements: R_M_014 */
    }
    part Command_Security_Concern : CommandSecurityConcern {
        doc /* Framed by the Mission Requirements: R_M_020 */
    }
    part Amateur_Radio_Access_Concern : AmateurRadioAccessConcern {
        doc /* Framed by the Mission Requirements: R_M_017 */
    }
    part Programmatic_Compliance_Concern : ProgrammaticComplianceConcern {
        doc /* Framed by the Mission Requirements: R_M_002, R_M_006, R_M_009, R_M_010, R_M_011, R_M_012, R_M_013, R_M_015 */
    }
    part Team_Composition_Concern : TeamCompositionConcern {
        doc /* Framed by the Mission Requirements: R_M_009, R_M_010 */
    }
    part Registration_Compliance_Concern : RegistrationComplianceConcern {
        doc /* Framed by the Mission Requirements: R_M_004, R_M_018 */
    }
}
