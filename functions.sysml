package HEALIOS_Functions {

    public action def PerformScienceOperations; // payload operations
    public action def OperateSystem; // ground Segment
    public action def MaintainOperability; //space Segment bus
    
}
