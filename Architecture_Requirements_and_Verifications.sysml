// TO DO:
    // Check Space Segment and Ground Segment requirements for compliance.
    // Check that all Space Segment and Ground Segment requirements are correctly linked to the higher-level.
    // Check that all requirements are correctly linked to the relevant stakeholders and concerns.
// At the end:
    // Do satifaction and verification implementation.
    // Add additional tracability between requirements... Look for keywords like dependency or trace.
    
package MissionLevelRequirementsPackage{
    private import MissionPackage::*;
    private import StakeholdersDefinitionPackage::*;
    private import ConcernsDefinitionPackage::*;
    private import StakeholderConcernsPackage::*;
    //private import SpaceSegmentLevelRequirementPackage::*;
    //private import GroundSegmentLevelRequirementsPackage::*;
    
    requirement def <R_M_001> Self_Healing_Experiments { 
        doc /* The mission shall perform active self-healing experiments on designated PSC samples by applying a controlled reverse-bias voltage during orbital eclipse phases. */

        subject HEALIOS_Mission references HealiosMissionInstancePackage::HEALIOS_Mission;
        
        frame concern Perovskite_TRL_Advancement_Concern references StakeholderConcernsPackage::Perovskite_TRL_Advancement_Concern;
        frame concern Perovskite_Investigation_Concern references StakeholderConcernsPackage::Perovskite_Investigation_Concern;
        frame concern Comparative_Study_Concern references StakeholderConcernsPackage::Comparative_Study_Concern;
        frame concern Data_Acquisition_Concern references StakeholderConcernsPackage::Data_Acquisition_Concern;
        frame concern Data_Availability_Concern references StakeholderConcernsPackage::Data_Availability_Concern;

        requirement <R_M_001_a> Self_Healing_Cycle {
            doc /* The mission shall implement a self-healing cycle that applies reverse-bias voltage to selected perovskite solar cells during eclipse periods. */
        }
        requirement <R_M_001_b> PSC_Performance {
            doc /* The mission shall characterise the performance of Perovskite Solar Cells (PSC) by measuring open-circuit voltage and short-circuit current, what results in Current-Voltage (I-V) curves. */
        }
        requirement <R_M_001_c> Control_Group_Benchmark {
            doc /* The mission shall utilise traditional solar cells as a control group to benchmark the degradation rates of the perovskite payload. */
        }
        requirement <R_M_001_d> Environment_Characterisation {
            doc /* The mission shall characterise the space environment by measuring radiation, irradiance, and temperature related to Perovskite Solar Cells samples, to contextualise with observed degradation and self-healing phenomena. */
        }
        requirement <R_M_001_e> Environmental_Repeatability {
            doc /* The mission scenarios shall enable repetitive environmental conditions for the perovskite solar cells and the benchmark group. */
        }
        requirement <R_M_001_f> Data_Management {
            doc /* The mission shall implement a data management strategy to ensure the integrity, accessibility, and usability of collected data for analysis and publication. */
        }
        requirement <R_M_001_g> Autonomous_Management {
            doc /* The mission shall autonomously manage experiment execution, including eclipse detection and data logging, to mitigate limited ground contact time. */
        }
    }

    requirement def <R_M_002> Orbit_Definition { 
            doc
            /* The mission shall be operated in the Low Earth Orbit (LEO). */
            
            subject Healios_Mission references HealiosMissionInstancePackage::HEALIOS_Mission;

            frame concern Perovskite_TRL_Advancement_Concern references StakeholderConcernsPackage::Perovskite_TRL_Advancement_Concern;
            frame concern Programmatic_Compliance_Concern references StakeholderConcernsPackage::Programmatic_Compliance_Concern;
            frame concern Component_Reliability_Concern references StakeholderConcernsPackage::Component_Reliability_Concern;
    }

    requirement def <R_M_003> Mission_Duration { 
        doc /* The mission shall operate in orbit for a duration sufficient to generate statistically significant degradation and recovery data (Target: 1 Year). */
        
        subject Healios_Mission references HealiosMissionInstancePackage::HEALIOS_Mission;

        frame concern Component_Reliability_Concern references StakeholderConcernsPackage::Component_Reliability_Concern;
        frame concern Perovskite_TRL_Advancement_Concern references StakeholderConcernsPackage::Perovskite_TRL_Advancement_Concern;
    }

    requirement def <R_M_004> Platform_Conformity {
        doc /* The mission should utilise a 1U CubeSat platform, conformant to CubeSat Design Specification Rev. 14.1 (February 2022), which enables experiment performance. */
        subject Healios_Mission references HealiosMissionInstancePackage::HEALIOS_Mission; 

        frame concern CubeSat_Standard_Compliance_Concern references StakeholderConcernsPackage::CubeSat_Standard_Compliance_Concern;
    }

    requirement def <R_M_005> Dataset_Format { // NOT IN SPACE SEGMENT
        doc /* The mission shall provide experiment datasets in a format and with metadata completeness necessary to support post-flight comparison to pre-flight terrestrial testing, and published literature. */
        
        subject Healios_Mission references HealiosMissionInstancePackage::HEALIOS_Mission;

        frame concern Data_Availability_Concern references StakeholderConcernsPackage::Data_Availability_Concern;
        frame concern Comparative_Study_Concern references StakeholderConcernsPackage::Comparative_Study_Concern;
    }

    requirement def <R_M_006> ESA_Compliance {
        doc /* The mission shall comply with the programmatic and safety standards of the ESA "Fly Your Satellite!" programme. */
        
        subject Healios_Mission references HealiosMissionInstancePackage::HEALIOS_Mission;

        frame concern Programmatic_Compliance_Concern references StakeholderConcernsPackage::Programmatic_Compliance_Concern;
    }

    requirement def <R_M_007> EOL_Plan {
        doc /* The mission documentation shall provide an EOL plan and update its relevance and applicability. */
        
        subject Healios_Mission references HealiosMissionInstancePackage::HEALIOS_Mission;

        frame concern Space_Debris_Mitigation_Concern references StakeholderConcernsPackage::Space_Debris_Mitigation_Concern;
    }

    requirement def <R_M_008> Core_Team_Composition { // NOT IN SPACE SEGMENT 
        doc /* The core mission team shall consist of at least 4 university students enrolled in a Master's or Bachelor's programme within an ESA Member State. */
        
        subject Healios_Mission references HealiosMissionInstancePackage::HEALIOS_Mission;
        
        frame concern Institutional_Visibility_Concern references StakeholderConcernsPackage::Institutional_Visibility_Concern;
        frame concern Educational_Value_Concern references StakeholderConcernsPackage::Educational_Value_Concern;
        frame concern Programmatic_Compliance_Concern references StakeholderConcernsPackage::Programmatic_Compliance_Concern;
        frame concern Team_Composition_Concern references StakeholderConcernsPackage::Team_Composition_Concern;
    }

    requirement def <R_M_009> Academic_Supervision { // NOT IN SPACE SEGMENT 
        doc /* The project shall be supervised by at least 2 academic professors or lecturers who provide formal endorsement and access to university facilities. */
        
        subject Healios_Mission references HealiosMissionInstancePackage::HEALIOS_Mission;

        frame concern Institutional_Visibility_Concern references StakeholderConcernsPackage::Institutional_Visibility_Concern;
        frame concern Programmatic_Compliance_Concern references StakeholderConcernsPackage::Programmatic_Compliance_Concern;
        frame concern Team_Composition_Concern references StakeholderConcernsPackage::Team_Composition_Concern;
    }

    requirement def <R_M_010> Academic_Integration { // NOT IN SPACE SEGMENT 
        doc /* The mission team shall identify specific thesis topics or academic credits associated with the project work packages. */
        subject Healios_Mission references HealiosMissionInstancePackage::HEALIOS_Mission;

        frame concern Institutional_Visibility_Concern references StakeholderConcernsPackage::Institutional_Visibility_Concern;
        frame concern Educational_Value_Concern references StakeholderConcernsPackage::Educational_Value_Concern;
        frame concern Programmatic_Compliance_Concern references StakeholderConcernsPackage::Programmatic_Compliance_Concern;
    }

    requirement def <R_M_011> Test_Facility_Usage {  // NOT IN GROUND SEGMENT
        doc /* The mission documentation shall include the use of ESA environmental test facilities (e.g., Thermal Vacuum Chamber, Electrodynamic Shaker). */
        subject Healios_Mission references HealiosMissionInstancePackage::HEALIOS_Mission;

        frame concern Institutional_Visibility_Concern references StakeholderConcernsPackage::Institutional_Visibility_Concern;
        frame concern Programmatic_Compliance_Concern references StakeholderConcernsPackage::Programmatic_Compliance_Concern;
        frame concern Component_Reliability_Concern references StakeholderConcernsPackage::Component_Reliability_Concern;
    }

    requirement def <R_M_012> Educational_Return { // NOT IN SPACE SEGMENT
        doc /* The mission shall demonstrate a clear educational return. */
        subject Healios_Mission references HealiosMissionInstancePackage::HEALIOS_Mission;

        frame concern Institutional_Visibility_Concern references StakeholderConcernsPackage::Institutional_Visibility_Concern;
        frame concern Educational_Value_Concern references StakeholderConcernsPackage::Educational_Value_Concern;
        frame concern Programmatic_Compliance_Concern references StakeholderConcernsPackage::Programmatic_Compliance_Concern;
    }

    requirement def <R_M_013> Ground_Station_Support {
        doc /* The mission shall include at least one operational Ground Station capable of commanding and receiving telemetry from the CubeSat. */
        
        subject Healios_Mission references HealiosMissionInstancePackage::HEALIOS_Mission;

        frame concern Link_Compatibility_Concern references StakeholderConcernsPackage::Link_Compatibility_Concern;
    }

    requirement def <R_M_014> Safety_Implementation {
        doc /* The mission plan and procedures shall ensure the safety of personnel, equipment, and the launch vehicle by implementing hazard control measures and complying with the safety requirements of the launch provider and test facilities. */
        
        subject Healios_Mission references HealiosMissionInstancePackage::HEALIOS_Mission;

        frame concern Safety_Concern references StakeholderConcernsPackage::Safety_Concern;
        frame concern Programmatic_Compliance_Concern references StakeholderConcernsPackage::Programmatic_Compliance_Concern;
    }

    requirement def <R_M_015> Launcher_Compliance { // NOT IN GROUND SEGMENT
        doc /* The mission architecture and organisation shall comply with the requirements of the selected launch service provider. */
        
        subject Healios_Mission references HealiosMissionInstancePackage::HEALIOS_Mission;

        frame concern Safety_Concern references StakeholderConcernsPackage::Safety_Concern;
    }

    requirement def <R_M_016> Telecommunication_Compliance {
        doc /* The mission architecture and organisation shall comply with International Telecommunication Union (ITU) and International Amatour Radio Union legislations. */
        
        subject Healios_Mission references HealiosMissionInstancePackage::HEALIOS_Mission;

        frame concern Frequency_Allocation_Concern references StakeholderConcernsPackage::Frequency_Allocation_Concern;
        frame concern Amateur_Radio_Access_Concern references StakeholderConcernsPackage::Amateur_Radio_Access_Concern;
    }

    requirement def <R_M_017> National_Legislation_Compliance { // NOT IN SPACE SEGMENT 
        doc /* The mission shall comply with national legislation of both Germany and Poland. */
        subject Healios_Mission references HealiosMissionInstancePackage::HEALIOS_Mission;

        frame concern Registration_Compliance_Concern references StakeholderConcernsPackage::Registration_Compliance_Concern;
    }

    requirement def <R_M_018> UN_Registration { // NOT IN SPACE SEGMENT // NOT IN GROUND SEGMENT
        doc /* The mission shall provide registration of the satellite in the United Nations Register of Objects Launched into Outer Space of UNOOSA, including national registers. */
        subject Healios_Mission references HealiosMissionInstancePackage::HEALIOS_Mission;

        frame concern Space_Debris_Mitigation_Concern references StakeholderConcernsPackage::Space_Debris_Mitigation_Concern;
        frame concern Registration_Compliance_Concern references StakeholderConcernsPackage::Registration_Compliance_Concern;

    }

    requirement def <R_M_019> FDIR_Implementation { 
        doc /* The mission shall implement a Fault Detection, Isolation, and Recovery (FDIR) strategy to enhance system reliability. */
        subject Healios_Mission references HealiosMissionInstancePackage::HEALIOS_Mission;

        frame concern Component_Reliability_Concern references StakeholderConcernsPackage::Component_Reliability_Concern;
    }

    requirement def <R_M_020> Security_Architecture {
        doc /* The mission shall implement secure data transmission link and relevant protection mechanisms to ensure the integrity against external threats, unauthorized access, and invalid data ingestion. */

        subject HEALIOS_Mission references HealiosMissionInstancePackage::HEALIOS_Mission;

        frame concern Command_Security_Concern references StakeholderConcernsPackage::Command_Security_Concern;
    }

    requirement def <R_M_021> Autonomous_Operations { 
        doc /* The mission shall be capable of autonomous operation, ensuring continuous execution of mission phases, maintenance of system safety, and survival without requiring continuous intervention from the ground segment. */
        
        subject HEALIOS_Mission references HealiosMissionInstancePackage::HEALIOS_Mission;

        frame concern Component_Reliability_Concern references StakeholderConcernsPackage::Component_Reliability_Concern;
        frame concern Perovskite_Investigation_Concern references StakeholderConcernsPackage::Perovskite_Investigation_Concern;
    }
}

package SpaceSegmentLevelRequirementPackage{
    private import MissionLevelRequirementsPackage::*;
    private import StakeholdersDefinitionPackage::*;
    private import ConcernsDefinitionPackage::*;
    private import StakeholderConcernsPackage::*;
    private import MissionPackage::*;
    //private import GroundSegmentLevelRequirementsPackage::*;


    requirement def <R_SS_001> SS_Self_Healing_Experiments specializes R_M_001 {
        doc /* The Space Segment shall enable active self-healing experiment performance on designated PSC samples by applying a controlled reverse-bias voltage during orbital eclipse phases. */
        subject Space_Segment references HealiosMissionInstancePackage::HEALIOS_Mission.HEALIOS_Space_Segment;

        requirement <R_SS_001_a> Payload_Accommodation {
            doc /* The Space Segment shall accommodate and support the operation of the perovskite solar cells payload. */
        }

        requirement <R_SS_001_b> PV_Data_Gathering {
            doc /* The Space Segment shall autonomously gather, store, and timestamp electrical performance data (Voltage, Current) of all photovoltaic technologies onboard throughout the mission, with a frequency higher than once per orbit. */
        }

        requirement <R_SS_001_c> Environment_Logging {

            doc /* The Space Segment shall log orbital environment parameters: thermal state, illumination condition, time since deployment, with a frequency higher than once per orbit. */
        }

        requirement <R_SS_001_d> Voltage_Range {
                doc /* The Space Segment shall be capable to apply a reverse-bias voltage  to selected perovskite solar cells during eclipse periods in the range of 0 to -5 V with a resolution of at least 0.1 V. */
            }

        requirement <R_SS_001_e> Reverse_Bias_Safety {
                doc /* The Space Segment shall ensure that reverse-bias conditions applied during self-healing cycles over the mission lifetime do not exceed material degradation thresholds of solar cells. */
        }

        requirement <R_SS_001_f> Sun_Pointing {
            doc /* The Space Segment shall maintain a sun-pointing attitude during the illuminated orbital phase to ensure consistent environmental conditions for the payload. */
        }

        requirement <R_SS_001_g> Data_Storage {
            doc /* The Space Segment shall have sufficient onboard data storage capacity to store all collected data between ground contacts, with redundancy to prevent data loss. */
        }

        requirement <R_SS_001_h> Eclipse_Detection {
            doc /* The Space Segment shall autonomously detect orbital eclipse periods to trigger self-healing cycles. */
        }

        requirement <R_SS_001_i> Autonomous_Execution {
            doc /* The Space Segment shall maintain autonomous execution of the experiment timeline such that temporary loss of ground communication does not interrupt scheduled phases. */
        }
    }

    requirement def <R_SS_002> Environmental_Survival specializes R_M_002, R_M_003 {
        doc /* The Space Segment shall survive the ground and launch activities and operate in the LEO environment for the mission duration of at least one year. */
        subject Space_Segment references HealiosMissionInstancePackage::HEALIOS_Mission.HEALIOS_Space_Segment;
        
        requirement <R_SS_002_a> Ground_Survival {
            doc /* The Space Segment shall survive the ground environment before the Launch, including the logistics and transportation. */
        }
        requirement <R_SS_002_b> Launch_Survival {
            doc /* The Space Segment shall withstand the mechanical and thermal stresses of the launch environment, including vibrations, shocks, and acoustic loads. */
        }
        requirement <R_SS_002_c> LEO_Survival {
            doc /* The Space Segment shall withstand the thermal and radiation environment of Low Earth Orbit (LEO) for a minimum operational lifetime of one year. */
        }
    }
    
    requirement def <R_SS_003> Deployer_Compatibility specializes R_M_004, R_M_015 {
        doc /* The Space Segment shall be compatible with the deployer environment. */
        subject Space_Segment references HealiosMissionInstancePackage::HEALIOS_Mission.HEALIOS_Space_Segment;
    }

    requirement def <R_SS_004> Launch_Mass specializes R_M_004 {
        doc /* The Space Segment should have a total launch mass not exceeding 2 kg within 0.001 kg tolerance. */

        subject Space_Segment references HealiosMissionInstancePackage::HEALIOS_Mission.HEALIOS_Space_Segment;

        attribute CubeSat_Size : String = Space_Segment.CubeSat_Form_Factor;
        attribute Mass_Limit  : ISQ::MassValue = 2.0 [SI::kg];
        attribute Mass_Tolerance : ISQ::MassValue = 0.001 [SI::kg];
        attribute Actual_Mass : ISQ::MassValue = Space_Segment.Total_Mass;

        assume constraint {
            CubeSat_Size == "1U"
        }
        require constraint {
            (Actual_Mass > 0.0 [SI::kg]) and
            (Actual_Mass <= Mass_Limit + Mass_Tolerance)
        }
    }

    requirement def <R_SS_005> Form_Factor_Requirement specializes R_M_004 {
        doc /* The Space Segment shall conform to the 1U CubeSat form factor as defined by the CubeSat Design Specification. */
        subject Space_Segment references HealiosMissionInstancePackage::HEALIOS_Mission.HEALIOS_Space_Segment;

        attribute required_size : String = "1U";
        attribute actual_size : String = Space_Segment.CubeSat_Form_Factor;

        require constraint {
            actual_size == required_size
        }
    }

    requirement def <R_SS_006> FYS_System_Compliance specializes R_M_006 {
        doc /* The Space Segment shall conform to all applicable ESA Fly Your Satellite! (FYS) engineering, safety, and testing standards throughout its lifecycle. */
        
        subject Space_Segment references HealiosMissionInstancePackage::HEALIOS_Mission.HEALIOS_Space_Segment;

        requirement <R_SS_006_a> FYS_Testing_Compatibility {
            doc /* The Space Segment shall maintain compatibility with the Fly Your Satellite! testing flow, including environmental and functional test setups, providing necessary test ports and Ground Support Equipment (GSE) interfaces. */
        }
        requirement <R_SS_006_b> FYS_Safety_Implementation {
            doc /* The Space Segment shall provide a safety plan traced to all FYS safety requirements and procedures. */
        }
        requirement <R_SS_006_c> FYS_Review_Deliverables {
            doc /* The Space Segment design, verification data, and models shall be structured to directly support the generation of Technical Data Packages (TDP) required for FYS programmatic milestone reviews (e.g., CDR, MRR). */
        }
    }

    requirement def <R_SS_007> EOL_Compliance specializes R_M_007 {
        doc /* The Space Segment shall implement end-of-life (EOL) measures compliant with space debris mitigation guidelines, such as passivation and deorbiting strategies. */
        subject Space_Segment references HealiosMissionInstancePackage::HEALIOS_Mission.HEALIOS_Space_Segment;
    }

    requirement def <R_SS_008> PFM_Campaign specializes R_M_011 {
        doc /* The Space Segment shall undergo a Proto-Flight Model (PFM) test campaign, compatible with the FYS testing flow and standards. */
        subject Space_Segment references HealiosMissionInstancePackage::HEALIOS_Mission.HEALIOS_Space_Segment;
        
        requirement <R_SS_008_a> PFM_Exclusions {
            doc /* The Space Segment PFM shall not be subjected to Life Testing, Burst Pressure, and Electrostatic Discharge (ESD) qualification. */
        }
        requirement <R_SS_008_b> Random_Vibration {
            doc /* The Space Segment shall undergo a random vibration test on all three axes. */
        }
        requirement <R_SS_008_c> Sinusoidal_Vibration {
            doc /* The Space Segment shall undergo a sinusoidal vibration test. */
        }
        requirement <R_SS_008_d> Quasi_Static_Load {
            doc /* The Space Segment shall undergo a Quasi-static load test. */
        }
        requirement <R_SS_008_e> Thermal_Cycling {
            doc /* The Space Segment shall undergo thermal cycling ( TVAC). */
        }
        requirement <R_SS_008_f> Bakeout {
            doc /* The Space Segment shall undergo a bakeout campaign. */
        }
        requirement <R_SS_008_g> PFM_Testing_Safety {
            doc /* The Space Segment PFM test campaign shall be planned and executed to ensure the safety of personnel, equipment, and facilities. */
        }
    }

    requirement def <R_SS_009> Telemetry_Protocol specializes R_M_013, R_M_016 {
        doc /* The Space Segment shall transmit telemetry data compatible with the defined Ground Segment protocols to enable correlation with terrestrial data. */
        subject Space_Segment references HealiosMissionInstancePackage::HEALIOS_Mission.HEALIOS_Space_Segment;
    }

    requirement def <R_SS_010> Beacon_Signal specializes R_M_013 {
        doc /* The Space Segment shall transmit a beacon signal to facilitate initial tracking and acquisition by the Ground Segment. */
        subject Space_Segment references HealiosMissionInstancePackage::HEALIOS_Mission.HEALIOS_Space_Segment;
    }

    requirement def <R_SS_011> FDIR_Implementation specializes R_M_014, R_M_019, R_M_020 {
        doc /* The Space Segment shall provide Foult Detection, Isolation, and Recovery (FDIR) capability to ensure spacecraft safety and experiment integrity. */
        subject Space_Segment references HealiosMissionInstancePackage::HEALIOS_Mission.HEALIOS_Space_Segment;

        requirement <R_SS_011_a> Fault_Detection {
            doc /* The Space Segment shall implement fault detection mechanisms or architecture. */
        }
        requirement <R_SS_011_b> Fault_Isolation {
            doc /* The Space Segment shall implement fault isolation mechanisms or architecture. */
        }
        requirement <R_SS_011_c> Fault_Recovery {
            doc /* The Space Segment shall implement progressive fault recovery sequences that attempt subsystem restart before invoking full safe mode. */
        }
        requirement <R_SS_011_d> Software_Updates {
            doc /* The Space Segment shall provide the capability to apply software updates throught the mission. */
        }
        requirement <R_SS_011_e> Safe_Mode {
            doc /* The Space Segment shall implement a safe mode that maintains basic spacecraft health and beacon transmission while non-essential functions are suspended. */
        }
    }

    requirement def <R_SS_012> Materials_Standard specializes R_M_014 {
        doc /* The Space Segment shall be constructed using space-compatible materials that comply with outgassing (TML, CVCM) and workmanship standards to prevent contamination of launch vehicles and other payloads. */
        subject Space_Segment references HealiosMissionInstancePackage::HEALIOS_Mission.HEALIOS_Space_Segment;
    }

    requirement def <R_SS_013> Safety_Plan specializes R_M_014 {
        doc /* The Space Segment shall have a documented safety plan that identifies potential hazards, risk mitigation measures, and compliance with safety requirements of the launch provider and test facilities. */
        subject Space_Segment references HealiosMissionInstancePackage::HEALIOS_Mission.HEALIOS_Space_Segment;

        //dependency R_SS_013 to FYS_System_Compliance::FYS_Safety_Implementation; 
    }

    requirement def <R_SS_014> Secure_Data_Link specializes R_M_020 {
        doc /* The Space Segment shall provide secure data transmission capabilities to protect sensitive mission data from unauthorized access or tampering. */
        subject Space_Segment references HealiosMissionInstancePackage::HEALIOS_Mission.HEALIOS_Space_Segment;

        //dependency R_SS_014 to FDIR_Implementation;
    }

    requirement def <R_SS_015> Autonomous_Mode_Management specializes R_M_021 {
        doc /* The Space Segment shall autonomously manage its operational states, including deployment, nominal mode (sun and eclipse phases), and safe mode, without requiring ground intervention. */
        subject Space_Segment references HealiosMissionInstancePackage::HEALIOS_Mission.HEALIOS_Space_Segment;

        requirement <R_SS_015_a> Deployment_Transition {
            doc /* The Space Segment shall autonomously transition from deployment configuration to nominal mode or safe mode, starting mission timing sequences. */
        }
        requirement <R_SS_015_b> Nominal_Operations {
            doc /* The Space Segment shall autonomously transition between sun and eclipse phases during nominal mode based on power generation and orbital position. */
        }
        requirement <R_SS_015_c> Safe_Mode_Transition {
            doc /* The Space Segment shall autonomously transition to safe mode upon the detection of critical system anomalies. */
        }
    }
}

package GroundSegmentLevelRequirementsPackage {
 private import MissionPackage::*;
    private import MissionLevelRequirementsPackage::*;
    private import StakeholdersDefinitionPackage::*;
    private import ConcernsDefinitionPackage::*;
    private import StakeholderConcernsPackage::*;

    requirement def <R_GS_001> GS_Communications_Operations specializes R_M_002, R_M_013 {
        doc /* The Ground Segment shall provide the operational capability to acquire, command, and receive telemetry from the spacecraft during scheduled visibility windows. */
        subject Ground_Segment references HealiosMissionInstancePackage::HEALIOS_Mission.HEALIOS_Ground_Segment;

        requirement <R_GS_001_a> Bidirectional_Communication {
            doc /* The Ground Segment shall support telecommand uplink and telemetry downlink with the spacecraft. */
        }
        requirement <R_GS_001_b> Pass_Prediction_TLE {
            doc /* The Ground Segment shall generate and maintain pass predictions using orbit propagation consistent with TLE-based inputs, and shall update predictions when new TLE data becomes available. */
        }
       requirement <R_GS_001_c> Ground_Antenna_System {
            doc /* The Ground Segment shall provide an antenna system capable of tracking and receiving spacecraft radio signals during visibility windows in Low Earth Orbit (LEO). */
        }
        requirement <R_GS_001_d> Beacon_Acquisition_Support {
            doc /* The Ground Segment shall support initial acquisition using the spacecraft beacon, including decoding, identification, and logging of beacon receptions. */
        }
        requirement <R_GS_001_e> Session_Execution_Procedures {
            doc /* The Ground Segment shall define and follow procedures for session execution, including pre-pass configuration, in-pass operations, and post-pass data handling. */
        }
        requirement <R_GS_001_f> RF_Frontend_Capability {
            doc /* The Ground Segment shall provide RF front-end capability compatible with the spacecraft communication system, including the selected frequency band(s), modulation scheme, and data rates. */
        }
        requirement <R_GS_001_g> Link_Budget_Compliance {
            doc /* The Ground Segment antenna and RF system shall provide sufficient link performance to maintain communication with the spacecraft in LEO consistent with the mission link budget and required link margin. */
        }
    }

    requirement def <R_GS_002> GS_Health_Monitoring_And_Response specializes R_M_013 {
        doc /* The Ground Segment shall monitor spacecraft health telemetry during each visibility window and support anomaly detection and operational response. */
        subject Ground_Segment references HealiosMissionInstancePackage::HEALIOS_Mission.HEALIOS_Ground_Segment;

        requirement <R_GS_002_a> Near_RealTime_Health_Display {
            doc /* The Ground Segment shall provide near-real-time display of key spacecraft health parameters during each pass. */
        }
        requirement <R_GS_002_b> Limit_Checking_And_Alerts {
            doc /* The Ground Segment should implement telemetry limit checking and generate alerts for out-of-family parameters. */
        }
        requirement <R_GS_002_c> Anomaly_Ticketing_And_Log {
            doc /* The Ground Segment shall record anomalies, operator observations, and corrective actions in an operations log or ticketing mechanism. */
        }
    }

    requirement def <R_GS_003> GS_Security_Controls specializes R_M_020, R_M_013 {
        doc /* The Ground Segment shall implement security controls that prevent unauthorized commanding and protect mission data handling processes. */
        subject Ground_Segment references HealiosMissionInstancePackage::HEALIOS_Mission.HEALIOS_Ground_Segment;

        requirement <R_GS_003_a> Operator_Authentication {
            doc /* The Ground Segment shall require authenticated operator identity for all commanding actions. */
        }
        requirement <R_GS_003_b> Role_Based_Authorization {
            doc /* The Ground Segment shall enforce role-based access control for commanding functions and ground system configuration changes. */
        }
        requirement <R_GS_003_c> Key_Management_Procedures {
            doc /* The Ground Segment shall define and implement cryptographic key management procedures (generation, storage, rotation, revocation, and recovery) for secure commanding and related data handling. */
        }
        requirement <R_GS_003_d> Audit_Trail {
            doc /* The Ground Segment shall maintain an audit trail of commanding actions, operator sessions, and configuration changes, including timestamps and operator identity. */
        }
    }

    requirement def <R_GS_004> GS_Data_Management specializes R_M_005, R_M_003 {
        doc /* The Ground Segment shall receive, validate, store, and package mission datasets with the format and metadata completeness required for analysis and publication. */
        subject Ground_Segment references HealiosMissionInstancePackage::HEALIOS_Mission.HEALIOS_Ground_Segment;

        requirement <R_GS_004_a> Structured_Data_Archive {
            doc /* The Ground Segment shall store all scientific and housekeeping data in a structured archive for the mission lifetime and for at least 2 years after end-of-mission. */
        }
        requirement <R_GS_004_b> Dataset_Metadata_And_Versioning {
            doc /* The Ground Segment shall generate dataset packages including required metadata fields and dataset version identifiers necessary for post-flight comparison to pre-flight tests and literature. */
        }
        requirement <R_GS_004_c> Data_Format_And_Range_Validation {
            doc /* The Ground Segment shall automatically validate received data against the defined dataset grammar, types, and permissible ranges, and shall flag invalid data for review and re-request if applicable. */
        }
        requirement <R_GS_004_d> Backup_And_Restore {
            doc /* The Ground Segment should implement backup and restore procedures for the mission archive to mitigate data loss. */
        }
    }

    requirement def <R_GS_005> GS_Telecom_Compliance_Operations specializes R_M_016, R_M_013 {
        doc /* The Ground Segment shall operate the mission radio link in compliance with applicable ITU regulations and (if used) IARU coordination procedures. */
        subject Ground_Segment references HealiosMissionInstancePackage::HEALIOS_Mission.HEALIOS_Ground_Segment;

        requirement <R_GS_005_a> Frequency_Use_Documentation {
            doc /* The Ground Segment shall maintain frequency use documentation and operational constraints required by the applicable regulatory framework. */
        }
        requirement <R_GS_005_b> Operator_Practices {
            doc /* The Ground Segment shall implement operator practices consistent with the applicable service rules (including amateur service rules if applicable). */
        }
    }

    requirement def <R_GS_006> GS_Operations_Safety_Procedures specializes R_M_014 {
        doc /* The Ground Segment shall define and apply operational procedures ensuring safety of personnel and equipment during ground operations, including facility rules and RF safety practices. */
        subject Ground_Segment references HealiosMissionInstancePackage::HEALIOS_Mission.HEALIOS_Ground_Segment;

        requirement <R_GS_006_a> Facility_Rules_Compliance {
            doc /* Ground operations shall comply with facility safety rules and access constraints of the hosting institution(s). */
        }
        requirement <R_GS_006_b> RF_Safety_Practices {
            doc /* The Ground Segment shall define RF safety practices for transmitter operation, antenna access, and maintenance activities. */
        }
    }

    requirement def <R_GS_007> GS_Prelaunch_Link_Verification specializes R_M_013, R_M_006, R_M_002 {
        doc /* The Ground Segment shall verify communication readiness prior to launch using link budgets and representative end-to-end tests with the spacecraft (or an RF representative). */
        subject Ground_Segment references HealiosMissionInstancePackage::HEALIOS_Mission.HEALIOS_Ground_Segment;

        requirement <R_GS_007_a> Link_Budget_Estimation {
            doc /* The Ground Segment shall perform pre-launch link-budget estimation and verification using representative orbital profiles and expected spacecraft RF parameters. */
        }
        requirement <R_GS_007_b> EndToEnd_Communications_Test {
            doc /* The Ground Segment shall execute end-to-end communication tests prior to launch, demonstrating uplink commanding and downlink reception/decoding using representative configurations. */
        }
    }

     requirement def <R_GS_008> GS_Experiment_Support specializes R_M_001, R_M_013, R_M_005 {
        doc /* The Ground Segment shall support the self-healing experiment by enabling downlink acquisition of experiment data products and by supporting ground-initiated experiment reconfiguration and software update operations. */
        subject Ground_Segment references HealiosMissionInstancePackage::HEALIOS_Mission.HEALIOS_Ground_Segment;

        requirement <R_GS_008_a> Experiment_Data_Interface {
            doc /* The Ground Segment shall receive, decode, and store experiment telemetry and payload data through the defined spacecraft communication interface. */
        }
        requirement <R_GS_008_b> Experiment_Dataset_Packaging {
            doc /* The Ground Segment shall package experiment datasets with identifiers, timestamps, and metadata sufficient to support post-flight comparison to pre-flight testing and literature. */
        }
        requirement <R_GS_008_c> Experiment_Reconfiguration_Traceability {
            doc /* The Ground Segment shall support uplink of approved experiment configuration changes and shall record the applied configuration state and the time of application. */
        }
        requirement <R_GS_008_d> Software_Update_Operations_Support {
            doc /* The Ground Segment shall support spacecraft software update operations by maintaining update packages, version identifiers, delivery procedures, and an update operations log. */
        }
    }

    requirement def <R_GS_009> GS_End_Of_Life_Operations_Plan specializes R_M_007, R_M_013, R_M_014 {
        doc /* The Ground Segment shall define and execute an end-of-life (EOL) operations plan to safely conclude mission operations, preserve mission data, and apply required end-state configurations. */
        subject Ground_Segment references HealiosMissionInstancePackage::HEALIOS_Mission.HEALIOS_Ground_Segment;

        requirement <R_GS_009_a> Spacecraft_EO_Ops_Procedures {
            doc /* The Ground Segment shall define EOL commanding and communication procedures, including final contact attempts, final data downlink strategy, and end-state configuration command sequences if applicable. */
        }
        requirement <R_GS_009_b> Archive_Freeze_And_Preservation {
            doc /* The Ground Segment shall preserve and freeze mission datasets at end-of-mission, including archive integrity checks, metadata completeness review, and backup generation. */
        }
        requirement <R_GS_009_c> Ground_System_Closure {
            doc /* The Ground Segment shall define a closure plan for ground operations services, including decommissioning of operational accounts, revocation or retirement of cryptographic keys used for mission operations, and retention of operational logs. */
        }
    }

    requirement def <R_GS_010> GS_Fault_And_Anomaly_Management specializes R_M_019, R_M_013 {
        doc /* The Ground Segment shall support mission fault management by detecting anomalies from telemetry, recording events, and enabling execution of recovery procedures through commanding during ground contacts. */
        subject Ground_Segment references HealiosMissionInstancePackage::HEALIOS_Mission.HEALIOS_Ground_Segment;

        requirement <R_GS_010_a> Telemetry_Anomaly_Detection {
            doc /* The Ground Segment shall support detection of telemetry anomalies through limit checks, consistency checks, and operator review during each visibility window. */
        }
        requirement <R_GS_010_b> Recovery_Procedure_Support {
            doc /* The Ground Segment shall maintain and execute approved recovery procedures, including command sequences and verification steps, to support subsystem restart and safe state restoration. */
        }
        requirement <R_GS_010_c> Fault_History_Repository {
            doc /* The Ground Segment shall maintain a fault and anomaly history repository, including event timestamps, observed symptoms, actions taken, and outcomes for later analysis. */
        }
    }

    requirement def <R_GS_011> GS_Autonomous_Operations_Support specializes R_M_021, R_M_013 {
        doc /* The Ground Segment shall support autonomous spacecraft operations by maintaining command planning and operational practices suitable for limited or interrupted ground contact. */
        subject Ground_Segment references HealiosMissionInstancePackage::HEALIOS_Mission.HEALIOS_Ground_Segment;

        requirement <R_GS_011_a> Loss_Of_Contact_Operational_Planning {
            doc /* The Ground Segment shall maintain an operations concept and command planning approach that preserves spacecraft safety and experiment continuity in the event of missed contacts. */
        }
        requirement <R_GS_011_b> Command_Plan_Traceability {
            doc /* The Ground Segment shall document and trace command plans and configuration changes such that spacecraft behavior can be reconstructed during autonomous operation periods. */
        }
        requirement <R_GS_011_c> Autonomy_Performance_Assessment {
            doc /* The Ground Segment shall assess autonomous mode behavior using received telemetry and shall record any deviations and corrective planning actions. */
        }
    }

    requirement def <R_GS_012> GS_Operations_Roles_And_Data_Access specializes R_M_008, R_M_009, R_M_010, R_M_005, R_M_020, R_M_012 {
        doc /* The Ground Segment shall support operations by the HEALIOS student team and provide controlled access to mission data and operational tools for academic supervisors and thesis-related work. */
        subject Ground_Segment references HealiosMissionInstancePackage::HEALIOS_Mission.HEALIOS_Ground_Segment;

        requirement <R_GS_012_a> Student_Operations_Role {
            doc /* The Ground Segment shall provide operational user roles and access rights enabling the HEALIOS student team to conduct nominal commanding and data handling activities under defined procedures. */
        }
        requirement <R_GS_012_b> Supervisor_Access {
            doc /* The Ground Segment shall provide academic supervisors with access to mission data products and relevant operational records with privileges appropriate for supervision activities. */
        }
        requirement <R_GS_012_c> Data_Access_For_Academic_Work {
            doc /* The Ground Segment shall provide controlled access to mission datasets and metadata required for thesis topics and academic analysis, including data export mechanisms and dataset version traceability. */
        }
    }

    requirement def <R_GS_013> GS_National_Legislation_Compliance specializes R_M_017, R_M_005, R_M_020 {
        doc /* The Ground Segment shall implement operational and data handling practices compliant with applicable national legislation of Germany and Poland, including access control, data retention, and operational logging. */
        subject Ground_Segment references HealiosMissionInstancePackage::HEALIOS_Mission.HEALIOS_Ground_Segment;

        requirement <R_GS_013_a> Data_Access_Compliance {
            doc /* The Ground Segment shall enforce access control measures for mission datasets and operational tools in accordance with applicable national requirements. */
        }
        requirement <R_GS_013_b> Data_Retention_And_Deletion_Policy {
            doc /* The Ground Segment shall define and apply a data retention and deletion policy for mission datasets and operational logs consistent with applicable national requirements. */
        }
        requirement <R_GS_013_c> Operations_Log_Retention {
            doc /* The Ground Segment shall retain operational logs of commanding sessions and data deliveries to support compliance demonstration and incident investigation. */
        }
    }
}

package ProgrammaticLevelRequirementsPackage {
    private import MissionPackage::*;
    private import MissionLevelRequirementsPackage::*;
    private import StakeholdersDefinitionPackage::*;
    private import ConcernsDefinitionPackage::*;
    private import StakeholderConcernsPackage::*;

    requirement def <R_PR_001> Project_Team_Organization specializes R_M_008, R_M_009 {
        doc /* The HEALIOS project shall establish and maintain an organizational structure consisting of a core student team and academic supervisors to ensure educational goals and university support. */
        subject Healios_Mission references HealiosMissionInstancePackage::HEALIOS_Mission;

        requirement <R_PR_001_a> Core_Student_Team {
            doc /* The project management shall ensure the core team consists of a minimum of 4 university students enrolled in Master's or Bachelor's programmes within an ESA Member State throughout the project lifecycle. */
        }
        requirement <R_PR_001_b> Academic_Endorsement {
            doc /* The project shall secure and maintain formal endorsement from at least 2 academic professors or lecturers, ensuring access to necessary university facilities and laboratories. */
        }
        requirement <R_PR_001_c> Succession_Planning {
            doc /* The project shall implement a succession and knowledge-transfer plan to mitigate the risk of core student team members graduating or leaving before mission completion. */
        }
    }

    requirement def <R_PR_002> Academic_Integration_And_Return specializes R_M_010, R_M_012 {
        doc /* The project shall embed mission activities within the academic curricula of the participating universities to guarantee a measurable educational return. */
        subject Healios_Mission references HealiosMissionInstancePackage::HEALIOS_Mission;

        requirement <R_PR_002_a> Thesis_Mapping {
            doc /* The set of Bachelor's or Master's thesis topics proposals shall be aligned with the project's technical objectives and deliverables. */
        }
        requirement <R_PR_002_b> ECTS_Credits_Alignment {
            doc /* The project tasks shall be structured to allow participating students to earn ECTS credits (or equivalent academic credits) where applicable. */
        }
        requirement <R_PR_002_c> Educational_Reporting {
            doc /* The project shall generate educational return reports detailing student involvement, theses completed, and skills acquired, suitable for ESA and university stakeholders. */
        }
    }

    requirement def <R_PR_003> ESA_Programmatic_Compliance specializes R_M_006, R_M_011 {
        doc /* The project shall comply with all programmatic milestones, documentation standards, and facility usage requirements of the ESA "Fly Your Satellite!" (FYS) programme. */
        subject Healios_Mission references HealiosMissionInstancePackage::HEALIOS_Mission;

        requirement <R_PR_003_a> Milestone_Reviews {
            doc /* The project team shall prepare Technical Data Packages (TDP) and participate in mandatory FYS programmatic reviews (e.g., CDR, MRR, FRR). */
        }
        requirement <R_PR_003_b> ESA_Test_Facility_Coordination {
            doc /* The project management shall coordinate and document the planned use of ESA environmental test facilities (e.g., TVAC, Shaker) in accordance with FYS schedule constraints. */
        }
    }

    requirement def <R_PR_004> Legal_And_Regulatory_Compliance specializes R_M_016, R_M_017, R_M_018 {
        doc /* The project shall fulfill all international and national legal obligations regarding spectrum usage, space object registration, and launch coordination. */
        subject Healios_Mission references HealiosMissionInstancePackage::HEALIOS_Mission;

        requirement <R_PR_004_a> ITU_Frequency_Coordination {
            doc /* The project shall successfully complete the Advance Publication Information (API) and frequency coordination process through the International Telecommunication Union (ITU) and IARU (if amateur bands are used). */
        }
        requirement <R_PR_004_b> Space_Object_Registration {
            doc /* The project shall ensure the satellite is registered in the national registry of the launching state (Germany/Poland) and subsequently in the UNOOSA Register of Objects Launched into Outer Space. */
        }
        requirement <R_PR_004_c> Export_Control_Compliance {
            doc /* The project shall comply with applicable national and European export control regulations (e.g., dual-use goods) for the transport of the space segment and ground support equipment. */
        }
    }

    requirement def <R_PR_005> Launch_And_Safety_Coordination specializes R_M_014, R_M_015 {
        doc /* The project shall manage the interfaces and safety documentation required by the launch service provider and test facility operators. */
        subject Healios_Mission references HealiosMissionInstancePackage::HEALIOS_Mission;

        requirement <R_PR_005_a> Launch_Provider_Documentation {
            doc /* The project shall deliver all required Interface Control Documents (ICD) and compatibility matrices to the selected launch service provider on schedule. */
        }
        requirement <R_PR_005_b> Safety_Submission_Packages {
            doc /* The project shall generate and submit safety data packages proving hazard mitigation (e.g., battery safety, RF inhibition) to the launch authority and ESA safety panels. */
        }
    }

    requirement def <R_PR_006> End_Of_Life_Documentation specializes R_M_007 {
        doc /* The project shall establish and maintain a documented End-of-Life (EOL) plan ensuring compliance with space debris mitigation standards. */
        subject Healios_Mission references HealiosMissionInstancePackage::HEALIOS_Mission;

        requirement <R_PR_006_a> Debris_Mitigation_Assessment {
            doc /* The project shall produce a Space Debris Mitigation (SDM) assessment demonstrating the satellite will passively deorbit within the required regulatory timeframe (e.g., 25 years). */
        }
        requirement <R_PR_006_b> Passivation_Plan {
            doc /* The EOL documentation shall detail the specific operational procedures and timelines for permanently depleting energy sources (battery passivation) at the end of the mission. */
        }
    }
}
