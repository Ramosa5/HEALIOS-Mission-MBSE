package SpaceActionsPackage {
    private import ScalarValues::*;
    private import MissionPackage::*;
    private import ISQ::*;
    private import CommunicationsSystemPackage::*;

    alias OBS for MissionPackage::OnBoardStatus;
    action def PerformSpaceSegmentMission {}

    action def provideScientificMeasurements specializes PerformSpaceSegmentMission {
        in Perform_Scientific_Action_Command : MissionPackage::OnBoardCommand [0..*] {
            :>> type = "MeasurementCommand";
        }
        out Measured_Data : OBS [0..*];
    }

    action def applyControlledReverseBiasToPSC specializes provideScientificMeasurements {
        in apply_Reverse_Bias_Voltage_Command redefines Perform_Scientific_Action_Command;
        out voltage_Application_Status redefines Measured_Data;

        bind Apply_Reverse_Bias_Voltage.Apply_Reverse_Bias_Voltage_Command =
            apply_Reverse_Bias_Voltage_Command;
        flow from Apply_Reverse_Bias_Voltage.Reverse_Bias_Voltage to voltage_Application_Status;

        action Apply_Reverse_Bias_Voltage {
            in Apply_Reverse_Bias_Voltage_Command;
            out Reverse_Bias_Voltage : ISQ::SourceVoltageValue;
        }
    }

    action def MeasureIVCurvesOfPSC specializes provideScientificMeasurements {
        in measure_IV_Curves_Of_PSC_Command redefines Perform_Scientific_Action_Command;
        out measured_IV_Curves_Status redefines Measured_Data;

        bind Measure_IV_Curves_Of_PSC.Iv_Curves_Data = measure_IV_Curves_Of_PSC_Command;
        flow from Measure_IV_Curves_Of_PSC.Iv_Curves_Data to measured_IV_Curves_Status;

        action Measure_IV_Curves_Of_PSC {
            in Measure_IV_Curves_Of_PSC_Command;
            out Iv_Curves_Data : OBS;
        }
    }

    action def maintainMaximumPowerPoint specializes provideScientificMeasurements {
        in maintain_MPP_Command redefines Perform_Scientific_Action_Command;
        out mpp_Status redefines Measured_Data;

        bind Maintain_MPP.Maintain_MPP_Command = maintain_MPP_Command;
        flow from Maintain_MPP.Mpp_Data to mpp_Status;

        action Maintain_MPP {
            in Maintain_MPP_Command;
            out Mpp_Data : OBS;
        }
    }

    action def collectExperimentalData specializes provideScientificMeasurements {
        in collect_Experimental_Data_Command redefines Perform_Scientific_Action_Command;

        out measured_Radiation_Status redefines Measured_Data;
        out measured_Temperature_Status redefines Measured_Data;
        out measured_Spectrum_Status redefines Measured_Data;
        out measured_Irradiance_Status redefines Measured_Data;

        bind Measure_Radiation.Measure_Radiation_Command = collect_Experimental_Data_Command;
        bind Measure_Temperature.Measure_Temperature_Command = collect_Experimental_Data_Command;
        bind Measure_Spectrum.Measure_Spectrum_Command = collect_Experimental_Data_Command;
        bind Measure_Irradiance.Measure_Irradiance_Command = collect_Experimental_Data_Command;

        flow from Measure_Radiation.Radiation_Data to measured_Radiation_Status;
        flow from Measure_Temperature.Temperature_Data to measured_Temperature_Status;
        flow from Measure_Spectrum.Spectrum_Data to measured_Spectrum_Status;
        flow from Measure_Irradiance.Irradiance_Data to measured_Irradiance_Status;

        action Measure_Radiation {
            in Measure_Radiation_Command : MissionPackage::OnBoardCommand;
            out Radiation_Data : OBS;
        }
        action Measure_Temperature {
            in Measure_Temperature_Command : MissionPackage::OnBoardCommand;
            out Temperature_Data : OBS;
        }
        action Measure_Spectrum {
            in Measure_Spectrum_Command : MissionPackage::OnBoardCommand;
            out Spectrum_Data : OBS;
        }
        action Measure_Irradiance {
            in Measure_Irradiance_Command : MissionPackage::OnBoardCommand;
            out Irradiance_Data : OBS;
        }
    }

    // -----EPS

    action def ManageElectricalPower specializes PerformSpaceSegmentMission {
        in Eps_Command : MissionPackage::OnBoardCommand [0..*] { :>> type = "PowerCommand"; }
        out Eps_Telemetry : OBS [0..*];
    }

    action def performMPPT specializes ManageElectricalPower {
        in mppt_Command redefines Eps_Command;
        out Mppt_Status redefines Eps_Telemetry;

        bind Mppt_Controller.Mppt_Command = mppt_Command;
        flow from Mppt_Controller.Mppt_Telemetry to Mppt_Status;

        action Mppt_Controller {
            in Mppt_Command : MissionPackage::OnBoardCommand;
            out Mppt_Telemetry : OBS;
        }
    }

    action def manageBatteryEnergy specializes ManageElectricalPower {
        in battery_Command redefines Eps_Command;
        out battery_Status redefines Eps_Telemetry;

        bind Battery_Manager.Battery_Command = battery_Command;
        flow from Battery_Manager.Battery_Telemetry to battery_Status;

        action Battery_Manager {
            in Battery_Command : MissionPackage::OnBoardCommand;
            out Battery_Telemetry : OBS;
        }
    }

    action def distributePowerToLoads specializes ManageElectricalPower {
        in distribution_Command redefines Eps_Command;
        out distribution_Status redefines Eps_Telemetry;

        bind Power_Distributor.Distribution_Command = distribution_Command;
        flow from Power_Distributor.Distribution_Telemetry to distribution_Status;

        action Power_Distributor {
            in Distribution_Command : MissionPackage::OnBoardCommand;
            out Distribution_Telemetry : OBS;
        }
    }

    action def manageLoadSheddingAndReactivation specializes ManageElectricalPower {
        in load_Mgmt_Command redefines Eps_Command;
        out load_Mgmt_Status redefines Eps_Telemetry;

        bind Load_Manager.Load_Mgmt_Command = load_Mgmt_Command;
        flow from Load_Manager.Load_Mgmt_Telemetry to load_Mgmt_Status;

        action Load_Manager {
            in Load_Mgmt_Command : MissionPackage::OnBoardCommand;
            out Load_Mgmt_Telemetry : OBS;
        }
    }

    action def switchEPSState specializes ManageElectricalPower {
        in switch_Command redefines Eps_Command;
        out switch_Status redefines Eps_Telemetry;

        bind State_Switch.Switch_Command = switch_Command;
        flow from State_Switch.State_Telemetry to switch_Status;

        action State_Switch {
            in Switch_Command : MissionPackage::OnBoardCommand;
            out State_Telemetry : OBS;
        }
    }

    action def reportEPSHealth specializes ManageElectricalPower {
        in report_Command redefines Eps_Command;
        out health_Telemetry redefines Eps_Telemetry;

        bind Health_Reporter.Report_Command = report_Command;
        flow from Health_Reporter.Health_Data to health_Telemetry;

        action Health_Reporter {
            in Report_Command : MissionPackage::OnBoardCommand;
            out Health_Data : OBS;
        }
    }

    // obdh

    action def TimeTagData {
        in Data : OBS;
        in Time : ISQ::TimeValue;
        out Time_Tagged_Data : MissionPackage::TimeTaggedStatus;
    }

    action def PackData {
        in Time_Tagged_Data : MissionPackage::TimeTaggedStatus [0..*];
        out Data_Package : OBS [1];
    }

    action def PrepareData {
        out Time_Tagged_Packed_Data : OBS [0..*];
        in Data_In : OBS [0..*];
        in Current_Time : ISQ::TimeValue [1];
        attribute Subsystem_Count : Integer;

        first start;
        then action For_Loop
        for i : Integer in 1..Subsystem_Count {
            action Time_Tag_Data : TimeTagData;
            then action Pack_Data : PackData;
            succession flow from Time_Tag_Data.Time_Tagged_Data to Pack_Data.Time_Tagged_Data;
        }
    }

    action def ManagePersistentStorageAndBuffers {
        in Obdh_Command : MissionPackage::OnBoardCommand [0..*];
        out Obdh_Telemetry : OBS [0..*];

        in Hk_Records : OBS [0..*];
        in Science_Records : OBS [0..*];
        in Event_Records : OBS [0..*];

        out Stored_Ok : OBS [0..*];

        flow from Hk_Records to Stored_Ok;
        flow from Science_Records to Stored_Ok;
        flow from Event_Records to Stored_Ok;
        flow from Stored_Ok to Obdh_Telemetry;
    }

    action def SelectAndPrioritizeDownlinkData {
        in Obdh_Command : MissionPackage::OnBoardCommand [0..*];
        out Obdh_Telemetry : OBS [0..*];

        in Stored_Data_Index : OBS [0..*];
        in Link_Window_Info : OBS [0..*];

        out Downlink_Queue : OBS [0..*];

        flow from Stored_Data_Index to Downlink_Queue;
        flow from Downlink_Queue to Obdh_Telemetry;
    }

    action def ForwardDownlinkFramesToComms {
        in Obdh_Command : MissionPackage::OnBoardCommand [0..*];
        out Obdh_Telemetry : OBS [0..*];

        in Downlink_Queue : OBS [0..*];
        out Comm_Frames : OBS [0..*];

        flow from Downlink_Queue to Comm_Frames;
        flow from Comm_Frames to Obdh_Telemetry;
    }

    action def DecodeValidateAndDispatchCommands {
        in Obdh_Command : MissionPackage::OnBoardCommand [0..*];
        out Obdh_Telemetry : OBS [0..*];

        out Eps_Cmd : MissionPackage::OnBoardCommand [0..*];
        out Aocs_Cmd : MissionPackage::OnBoardCommand [0..*];
        out Tcs_Cmd : MissionPackage::OnBoardCommand [0..*];
        out Daq_Cmd : MissionPackage::OnBoardCommand [0..*];

        out Cmd_Accepted : OBS [0..*];
        out Cmd_Rejected : OBS [0..*];

        flow from Cmd_Accepted to Obdh_Telemetry;
        flow from Cmd_Rejected to Obdh_Telemetry;
    }

    action def ExecuteTimeTaggedCommands {
        in Obdh_Command : MissionPackage::OnBoardCommand [0..*];
        out Obdh_Telemetry : OBS [0..*];

        in Scheduled_Cmds : MissionPackage::OnBoardCommand [0..*];
        out Executed : OBS [0..*];

        flow from Executed to Obdh_Telemetry;
    }

    action def PerformOBDHHealthMonitoringAndFDIR {
        in Obdh_Command : MissionPackage::OnBoardCommand [0..*];
        out Obdh_Telemetry : OBS [0..*];

        in Hk_Inputs : OBS [0..*];
        out Fdir_Events : OBS [0..*];
        out Safe_Mode_Req : MissionPackage::OnBoardCommand [0..*];

        flow from Hk_Inputs to Fdir_Events;
        flow from Fdir_Events to Obdh_Telemetry;
    }

    action def ManageSpacecraftModesAndAutonomy {
        in Obdh_Command : MissionPackage::OnBoardCommand [0..*];
        out Obdh_Telemetry : OBS [0..*];

        in Power_State : OBS [0..*];
        in Thermal_State : OBS [0..*];
        in Fdir_Events : OBS [0..*];

        out Mode_Change : MissionPackage::OnBoardCommand [0..*];

        flow from Mode_Change to Obdh_Telemetry;
    }

    action def ManageWarmRedundantAuthorityAndTakeover {
        in Obdh_Command : MissionPackage::OnBoardCommand [0..*];
        out Obdh_Telemetry : OBS [0..*];

        in Primary_Heartbeat : OBS [0..*];
        in Sync_Updates : OBS [0..*];

        out Takeover_Declared : OBS [0..*];
        out Enter_Safe_Mode : MissionPackage::OnBoardCommand [0..*];

        flow from Takeover_Declared to Obdh_Telemetry;
    }

    action def SynchronizeRedundantOBCState {
        in Obdh_Command : MissionPackage::OnBoardCommand [0..*];
        out Obdh_Telemetry : OBS [0..*];

        in Current_State : OBS [0..*];
        out Sync_Packet : OBS [0..*];

        flow from Current_State to Sync_Packet;
        flow from Sync_Packet to Obdh_Telemetry;
    }

    action def PerformDualBankSoftwareUpdateAndRollback {
        in Obdh_Command : MissionPackage::OnBoardCommand [0..*];
        out Obdh_Telemetry : OBS [0..*];

        in Image_Packets : OBS [0..*];

        out Image_Verified : OBS [0..*];
        out Bank_Switched : OBS [0..*];
        out Rollback_Done : OBS [0..*];

        flow from Image_Verified to Obdh_Telemetry;
        flow from Bank_Switched to Obdh_Telemetry;
        flow from Rollback_Done to Obdh_Telemetry;
    }

    // tcs

    action def EvaluateThreshold {
        in Temp : ISQ::TemperatureValue;
        in Threshold : ISQ::TemperatureValue;
        out ref Turn_On : Boolean;

        if Temp > Threshold {
            assign Turn_On := false;
        } else {
            assign Turn_On := true;
        }
    }

    action def StartHeater {
        in Enable_Signal : Boolean;
        in Heater_Power_Value : ISQ::PowerValue;
        out ref Heater_Output : ISQ::PowerValue;

        if Enable_Signal {
            assign Heater_Output := Heater_Power_Value;
        } else {
            assign Heater_Output := 0 [SI::W];
        }
    }

    action def ControlTemperature {
        in Minimal_Temperature : ISQ::TemperatureValue;
        in Heating_Power : ISQ::PowerValue;
        in Temp_Reading : ISQ::TemperatureValue;

        action Evaluate : EvaluateThreshold {
            bind Temp = Temp_Reading;
            bind Threshold = Minimal_Temperature;
        }

        then action Heat : StartHeater {
            bind Heater_Power_Value = Heating_Power;
            bind Enable_Signal = Evaluate.Turn_On;
        }
    }

    action def UseTCS {
        in Command : OnBoardCommand;
        in Minimal_Temperature_Input : ISQ::TemperatureValue;
        in Measured_Temperature_Input : ISQ::TemperatureValue;
        in Heating_Power_Input : ISQ::PowerValue;

        // if Command.Type == "Start_Command" {
        // loop {
        perform action Read_Temperature : ReadTemperature {
            bind temp = Measured_Temperature_Input;
        }
        then perform action Control_Temperature : ControlTemperature {
            bind Control_Temperature.Minimal_Temperature = Minimal_Temperature_Input;
            bind Control_Temperature.Heating_Power = Heating_Power_Input;
            bind Control_Temperature.Temp_Reading = Read_Temperature.temp;
        }
        // } until Command.Type == "Stop_Command";
        // }
    }

    action def ReadTemperature {
        out temp : ISQ::TemperatureValue;
    }

    // aocs

    action def ReadSunAngle {
        out beta_Angle : ISQ::AngularMeasureValue;
    }

    action def UseMagnetorquer {
        in beta_Angle : ISQ::AngularMeasureValue;
        in threshold : ISQ::AngularMeasureValue;
        out force : ISQ::ForceValue;
    }

    action def CorrectAttitude {
        in force_Value : ISQ::ForceValue;
        in sun_Sensor_Reading : ISQ::AngularMeasureValue;
        in threshold : ISQ::AngularMeasureValue; // 0 to pi
        out force : ISQ::ForceValue;

        then action Use_Magnetorquer : UseMagnetorquer {
            bind UseMagnetorquer::threshold = CorrectAttitude::threshold;
            bind UseMagnetorquer::beta_Angle = sun_Sensor_Reading;
            bind UseMagnetorquer::force = CorrectAttitude::force;
            if beta_Angle > threshold {
                assign force := force_Value;
            } else {
                assign force := 0 [SI::N];
            }
        }
    }

    action def UseAOCS {
        in command : OnBoardCommand;
        in beta_Angle_Threshold : ISQ::AngularMeasureValue;
        out force_Output : ISQ::ForceValue;
        if command.type == "Start_Command" {
            loop {
                action read_Sun_Angle : ReadSunAngle;
                then action correct_Attitude : CorrectAttitude;
            } until command.type == "Stop_Command";
        }
    }

    action def TransmitStatusDownlink {
        in item Telemetry_Input : OBS;
        out item Transmitted_Radio_Signal : MissionPackage::TelemetryData;
    }

    action def DecryptAndAuthenticateUplink {
        in item Telemetry_To_Encrypt : MissionPackage::TelemetryData;
        out item cmdOut : MissionPackage::GroundCommand;
    }

    action def EncryptDownlinkTelemetry {
        in item Telemetry_To_Encrypt : MissionPackage::TelemetryData;
        out item Secured_Encrypted_Telemetry : MissionPackage::TelemetryData;
    }

    action def TransmitBeacon {
        out item Secured_Encrypted_Telemetry : MissionPackage::TelemetryData;
    }

    action def ArchiveAndStoreMissionData {
        in item Telemetry_To_Archive : MissionPackage::TelemetryData;
        out item Archived_Record : GroundStationPackage::ArchiveRecord;
    }

    // ----------------safe mode coomands

    action def Enter_Safe_Mode_Action specializes PerformSpaceSegmentMission {
        in Trigger_Command : MissionPackage::OnBoardCommand [0..*] { :>> type = "ErrorCommand"; }
        out Payload_Power_Off_Cmd : MissionPackage::OnBoardCommand [0..*] {
            :>> type = "PowerCommand";
        }
        out Safe_Mode_Cmd : MissionPackage::OnBoardCommand [0..*] { :>> type = "ModeCommand"; }
        out Safe_Mode_Status : OBS [0..*];

        action Shed_Payload_Loads : manageLoadSheddingAndReactivation;
        bind Shed_Payload_Loads.load_Mgmt_Command = Payload_Power_Off_Cmd;
        flow from Shed_Payload_Loads.load_Mgmt_Status to Safe_Mode_Status;
    }
}

package GroundActionsPackage {
    private import MissionPackage::*;
    private import ISQ::*;
    private import GroundStationPackage::*;
    private import MissionControlCentrePackage::*;

    action def ExecuteUplink {
        in item Secured_Command_Input : MissionPackage::GroundCommand;
        out item Modulated_Uplink_Signal : MissionPackage::TelemetryData;
    }

    action def ReceiveDownlink {
        out item Captured_Encrypted_Telemetry : MissionPackage::TelemetryData;
        in item Incoming_Radio_Signal : TelemetryData;
    }

    action def ComputeTracking {
        in item Satellite_plan : PassPlan;
        out item Tracking_Data : TrackingData;
    }

    action def StreamToArchive {
        in item Telemetry_To_Archive : MissionPackage::TelemetryData;
        out item Record_of_Telemetry : ArchiveRecord;
    }

    action def VerifyAndDecryptDownlink {
        in item Telemetry_To_Decrypt : MissionPackage::TelemetryData;
        out item Verified_Ground_Telemetry_Data : MissionPackage::TelemetryData;
    }

    action def AuthenticateAndEncryptUplink {
        in item Telecommand_To_Encrypt : MissionPackage::GroundCommand;
        out item Secured_Encrypted_Telecommand : MissionPackage::GroundCommand;
    }

    action def ValidateTelemetry {
        in item Telemetry_For_Validate : MissionPackage::TelemetryData;
        out item Validated_Telemetry : MissionPackage::TelemetryData;
    }

    action def StoreRecord {
        in item Record_of_Satellite_Data : ArchiveRecord;
    }

    action def AuthorizeCommanding {
        in item Access_Request_Input : OperatorRequest;
        out item Valid_Session_Token : AuthToken;
    }

    action def GenerateTelecommand {
        in item Session_Token_Input : AuthToken;
        out item Raw_Unsecured_Telecommand : MissionPackage::GroundCommand;
    }

    action def GeneratePassPlan {
        out item Plan_of_Satellite_Path : PassPlan;
    }

    action def MonitorTelemetryRealtime {
        in item Telemetry_For_Monitoring : MissionPackage::TelemetryData;
        out item Real_Time_Health_Display : TelemetryData;
    }

    action def GetScientificDatasets {
        doc
        /* Converts archive records into human-readable datasets. */

        in item Raw_Archive_Data_Input : ArchiveRecord;
        out item Validated_Scientific_Dataset : ProcessedScienceData;
    }

    action def FacilitateYouthDevelopement {
        doc
        /* Universities use the live mission data to facilitate student theses, laboratory exercises, and hands-on operational training. */

        in item Mission_Data_For_Students : ProcessedScienceData;
        out item Academic_Educational_Outcome : ProcessedScienceData;
    }

    action def AnalyzePerovskiteSelfHealingBehavior {
        doc
        /* Investigates the self-healing properties of perovskite solar cells 
         * in space by analyzing I-V curves and efficiency recovery during 
         * eclipse phases.
         */

        in item Dataset_For_Investigation : ProcessedScienceData;
        out item Self_Healing_Behaviour_Dataset : ProcessedScienceData;
    }

    action def BenchmarkDegradationAgainstSiliconStandards {
        doc
        /* Compares the degradation rates of perovskite solar cells against 
         * established traditional solar cell benchmarks (e.g., Triple-Junction 
         * Silicon) to evaluate performance and Technology Readiness Level (TRL).
         */

        in item Comparative_Data_Input : ProcessedScienceData;
        out item Benchmark_Results_Dataset : ProcessedScienceData;
    }
}
